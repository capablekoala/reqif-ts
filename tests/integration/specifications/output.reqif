This is a test file with specifications and hierarchies

# Specification: Test Document

## so-1: System Requirement 1
- This is requirement 1

### so-2: System Requirement 2
- This is requirement 2

## so-3: System Requirement 3
- This is requirement 3
